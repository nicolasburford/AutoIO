;;This file contains the commands to load components on startup.

(load "C:\\Drafting\\Custom\\AutoIO\\Lisp\\functions.lsp")
(princ "functions loaded successfully.\n")
(load "C:\\Drafting\\Custom\\AutoIO\\Lisp\\main.lsp")
(princ "main loaded successfully.\n")
(load "C:\\Drafting\\Custom\\AutoIO\\Lisp\\Srxtext.vlx")
(princ "Srxtext loaded successfully.\n")
(load "C:\\Drafting\\Custom\\AutoIO\\Lisp\\GetExcel.lsp")
(princ "GetExcel loaded successfully.\n")
(load "C:\\Drafting\\Custom\\AutoIO\\Lisp\\pfunctions.lsp")
(princ "pfunctions loaded successfully.\n")
(load "C:\\Drafting\\Custom\\AutoIO\\Lisp\\ffunctions.lsp")
(princ "ffunctions loaded successfully.\n")
(load "C:\\Drafting\\Custom\\AutoIO\\Lisp\\cfunctions.lsp")
(princ "cfunctions loaded successfully.\n")
(load "C:\\Drafting\\Custom\\AutoIO\\Lisp\\clfunctions.lsp")
(princ "clfunctions loaded successfully.\n")
(load "C:\\Drafting\\Custom\\AutoIO\\Lisp\\nfunctions.lsp")
(princ "nfunctions loaded successfully.\n")
(load "C:\\Drafting\\Custom\\AutoIO\\Lisp\\dialogboxes.lsp")
(princ "dialogboxes loaded successfully.\n")
(load "C:\\Drafting\\Custom\\AutoIO\\Lisp\\plc5functions.lsp")
(princ "plc5functions loaded successfully.\n")
(load "C:\\Drafting\\Custom\\AutoIO\\Lisp\\AutoIO Setup.lsp")
(princ "AutoIO Setup loaded successfully.\n")
(load "C:\\Drafting\\Custom\\AutoIO\\Lisp\\references.lsp")
(princ "references loaded successfully.\n")
(load "C:\\Drafting\\Custom\\AutoIO\\Lisp\\interconnect.lsp")
(princ "New Point loaded successfully.\n")
(load "C:\\Drafting\\Custom\\AutoIO\\Lisp\\npfunctions.lsp")
(princ "interconnect loaded successfully.\n")
(command "netload" "C:\\Drafting\\Custom\\AutoIO\\VB\\ACADEXCEL.dll")
(princ "ACADEXCEL loaded successfully.\n")
(command "netload" "C:\\Drafting\\Custom\\AutoIO\\VB\\Test Form For Hex.dll")

(princ "\nAutoIO loaded successfully.\n")
